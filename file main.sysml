package MainModel {
    doc /* My First SysML v2 Architecture Model */
    
    part def AircraftSystem;

    requirement def SafetyRequirement {
        doc /* The system must operate safely within defined limits. */
    }
}
